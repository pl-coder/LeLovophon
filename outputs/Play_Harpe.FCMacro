import FreeCAD as App, FreeCADGui as Gui, math, json, time
from FreeCAD import Vector as V
from PySide import QtCore
OUT='./outputs'
path=OUT+'/Harpe_d_Amour_Koto_Pendulums.FCStd'
doc=next((d for d in App.listDocuments().values() if d.FileName==path),None)
if doc is None:doc=App.openDocument(path)
App.setActiveDocument(doc.Name)
rows=json.loads(doc.Motion.LinkageGeometry)
styles={'Baseplate_310x170x6': {'color': [0.48, 0.3, 0.16], 'alpha': 1}, 'CommonInputShaft_D6': {'color': [0.73, 0.77, 0.8], 'alpha': 1}, 'LowInputStand0': {'color': [0.25, 0.3, 0.34], 'alpha': 1}, 'LowInputBearing0': {'color': [0.73, 0.77, 0.8], 'alpha': 1}, 'LowInputStand1': {'color': [0.25, 0.3, 0.34], 'alpha': 1}, 'LowInputBearing1': {'color': [0.73, 0.77, 0.8], 'alpha': 1}, 'LowGearboxTray': {'color': [0.25, 0.3, 0.34], 'alpha': 1}, 'C_RaisedArmShaft': {'color': [0.73, 0.77, 0.8], 'alpha': 1}, 'C_ExtendedArm': {'color': [0.75, 0.3, 0.28], 'alpha': 1}, 'C_ExtendedPick': {'color': [0.25, 0.3, 0.34], 'alpha': 1}, 'D_RaisedArmShaft': {'color': [0.73, 0.77, 0.8], 'alpha': 1}, 'D_ExtendedArm': {'color': [0.82, 0.55, 0.22], 'alpha': 1}, 'D_ExtendedPick': {'color': [0.25, 0.3, 0.34], 'alpha': 1}, 'E_RaisedArmShaft': {'color': [0.73, 0.77, 0.8], 'alpha': 1}, 'E_ExtendedArm': {'color': [0.35, 0.65, 0.45], 'alpha': 1}, 'E_ExtendedPick': {'color': [0.25, 0.3, 0.34], 'alpha': 1}, 'F_RaisedArmShaft': {'color': [0.73, 0.77, 0.8], 'alpha': 1}, 'F_ExtendedArm': {'color': [0.28, 0.53, 0.76], 'alpha': 1}, 'F_ExtendedPick': {'color': [0.25, 0.3, 0.34], 'alpha': 1}, 'G_RaisedArmShaft': {'color': [0.73, 0.77, 0.8], 'alpha': 1}, 'G_ExtendedArm': {'color': [0.59, 0.38, 0.72], 'alpha': 1}, 'G_ExtendedPick': {'color': [0.25, 0.3, 0.34], 'alpha': 1}, 'SoundboxShell': {'color': [0.48, 0.3, 0.16], 'alpha': 1}, 'SoundboxEndBlock0': {'color': [0.48, 0.3, 0.16], 'alpha': 1}, 'SoundboxEndBlock1': {'color': [0.48, 0.3, 0.16], 'alpha': 1}, 'SoundboxFoot0': {'color': [0.48, 0.3, 0.16], 'alpha': 1}, 'SoundboxFoot1': {'color': [0.48, 0.3, 0.16], 'alpha': 1}, 'SoundboxFoot2': {'color': [0.48, 0.3, 0.16], 'alpha': 1}, 'SoundboxFoot3': {'color': [0.48, 0.3, 0.16], 'alpha': 1}, 'A_RaisedArmShaft': {'color': [0.73, 0.77, 0.8], 'alpha': 1}, 'A_ExtendedArm': {'color': [0.25, 0.69, 0.69], 'alpha': 1}, 'A_ExtendedPick': {'color': [0.25, 0.3, 0.34], 'alpha': 1}, 'CommonIntermediateAxle': {'color': [0.25, 0.3, 0.34], 'alpha': 1}, 'IntermediateAxleStand0': {'color': [0.25, 0.3, 0.34], 'alpha': 1}, 'IntermediateAxleStand1': {'color': [0.25, 0.3, 0.34], 'alpha': 1}, 'C_RatioDrivePulley': {'color': [0.8, 0.63, 0.3], 'alpha': 1}, 'C_RatioDrivenPulley': {'color': [0.8, 0.63, 0.3], 'alpha': 1}, 'C_CompoundPulleyHub': {'color': [0.8, 0.63, 0.3], 'alpha': 1}, 'C_IndependentPulleyBearing': {'color': [0.8, 0.63, 0.3], 'alpha': 1}, 'C_RatioBelt': {'color': [0.1, 0.11, 0.12], 'alpha': 1}, 'D_RatioDrivePulley': {'color': [0.8, 0.63, 0.3], 'alpha': 1}, 'D_RatioDrivenPulley': {'color': [0.8, 0.63, 0.3], 'alpha': 1}, 'D_CompoundPulleyHub': {'color': [0.8, 0.63, 0.3], 'alpha': 1}, 'D_IndependentPulleyBearing': {'color': [0.8, 0.63, 0.3], 'alpha': 1}, 'D_RatioBelt': {'color': [0.1, 0.11, 0.12], 'alpha': 1}, 'E_RatioDrivePulley': {'color': [0.8, 0.63, 0.3], 'alpha': 1}, 'E_RatioDrivenPulley': {'color': [0.8, 0.63, 0.3], 'alpha': 1}, 'E_CompoundPulleyHub': {'color': [0.8, 0.63, 0.3], 'alpha': 1}, 'E_IndependentPulleyBearing': {'color': [0.8, 0.63, 0.3], 'alpha': 1}, 'E_RatioBelt': {'color': [0.1, 0.11, 0.12], 'alpha': 1}, 'F_RatioDrivePulley': {'color': [0.8, 0.63, 0.3], 'alpha': 1}, 'F_RatioDrivenPulley': {'color': [0.8, 0.63, 0.3], 'alpha': 1}, 'F_CompoundPulleyHub': {'color': [0.8, 0.63, 0.3], 'alpha': 1}, 'F_IndependentPulleyBearing': {'color': [0.8, 0.63, 0.3], 'alpha': 1}, 'F_RatioBelt': {'color': [0.1, 0.11, 0.12], 'alpha': 1}, 'G_RatioDrivePulley': {'color': [0.8, 0.63, 0.3], 'alpha': 1}, 'G_RatioDrivenPulley': {'color': [0.8, 0.63, 0.3], 'alpha': 1}, 'G_CompoundPulleyHub': {'color': [0.8, 0.63, 0.3], 'alpha': 1}, 'G_IndependentPulleyBearing': {'color': [0.8, 0.63, 0.3], 'alpha': 1}, 'G_RatioBelt': {'color': [0.1, 0.11, 0.12], 'alpha': 1}, 'A_RatioDrivePulley': {'color': [0.8, 0.63, 0.3], 'alpha': 1}, 'A_RatioDrivenPulley': {'color': [0.8, 0.63, 0.3], 'alpha': 1}, 'A_CompoundPulleyHub': {'color': [0.8, 0.63, 0.3], 'alpha': 1}, 'A_IndependentPulleyBearing': {'color': [0.8, 0.63, 0.3], 'alpha': 1}, 'A_RatioBelt': {'color': [0.1, 0.11, 0.12], 'alpha': 1}, 'KotoAnchorBlock': {'color': [0.48, 0.3, 0.16], 'alpha': 1}, 'KotoAnchorSaddleRail': {'color': [0.8, 0.63, 0.3], 'alpha': 1}, 'KotoTunerBlock': {'color': [0.48, 0.3, 0.16], 'alpha': 1}, 'KotoTunerSaddleRail': {'color': [0.8, 0.63, 0.3], 'alpha': 1}, 'C_KotoSpeakingString': {'color': [0.92, 0.96, 1], 'alpha': 1}, 'C_KotoBackString': {'color': [0.92, 0.96, 1], 'alpha': 1}, 'C_KotoThirdBridge': {'color': [0.48, 0.3, 0.16], 'alpha': 1}, 'C_KotoAnchorSaddle': {'color': [0.8, 0.63, 0.3], 'alpha': 1}, 'C_KotoAnchorPin': {'color': [0.73, 0.77, 0.8], 'alpha': 1}, 'C_KotoAnchorTail': {'color': [0.92, 0.96, 1], 'alpha': 1}, 'C_KotoTunerSaddle': {'color': [0.8, 0.63, 0.3], 'alpha': 1}, 'C_KotoTunerPin': {'color': [0.73, 0.77, 0.8], 'alpha': 1}, 'C_KotoTunerTail': {'color': [0.92, 0.96, 1], 'alpha': 1}, 'C_PendulumBracket0': {'color': [0.25, 0.3, 0.34], 'alpha': 1}, 'C_PendulumBearing0': {'color': [0.73, 0.77, 0.8], 'alpha': 1}, 'C_PendulumBracket1': {'color': [0.25, 0.3, 0.34], 'alpha': 1}, 'C_PendulumBearing1': {'color': [0.73, 0.77, 0.8], 'alpha': 1}, 'D_KotoSpeakingString': {'color': [0.92, 0.96, 1], 'alpha': 1}, 'D_KotoBackString': {'color': [0.92, 0.96, 1], 'alpha': 1}, 'D_KotoThirdBridge': {'color': [0.48, 0.3, 0.16], 'alpha': 1}, 'D_KotoAnchorSaddle': {'color': [0.8, 0.63, 0.3], 'alpha': 1}, 'D_KotoAnchorPin': {'color': [0.73, 0.77, 0.8], 'alpha': 1}, 'D_KotoAnchorTail': {'color': [0.92, 0.96, 1], 'alpha': 1}, 'D_KotoTunerSaddle': {'color': [0.8, 0.63, 0.3], 'alpha': 1}, 'D_KotoTunerPin': {'color': [0.73, 0.77, 0.8], 'alpha': 1}, 'D_KotoTunerTail': {'color': [0.92, 0.96, 1], 'alpha': 1}, 'D_PendulumBracket0': {'color': [0.25, 0.3, 0.34], 'alpha': 1}, 'D_PendulumBearing0': {'color': [0.73, 0.77, 0.8], 'alpha': 1}, 'D_PendulumBracket1': {'color': [0.25, 0.3, 0.34], 'alpha': 1}, 'D_PendulumBearing1': {'color': [0.73, 0.77, 0.8], 'alpha': 1}, 'E_KotoSpeakingString': {'color': [0.92, 0.96, 1], 'alpha': 1}, 'E_KotoBackString': {'color': [0.92, 0.96, 1], 'alpha': 1}, 'E_KotoThirdBridge': {'color': [0.48, 0.3, 0.16], 'alpha': 1}, 'E_KotoAnchorSaddle': {'color': [0.8, 0.63, 0.3], 'alpha': 1}, 'E_KotoAnchorPin': {'color': [0.73, 0.77, 0.8], 'alpha': 1}, 'E_KotoAnchorTail': {'color': [0.92, 0.96, 1], 'alpha': 1}, 'E_KotoTunerSaddle': {'color': [0.8, 0.63, 0.3], 'alpha': 1}, 'E_KotoTunerPin': {'color': [0.73, 0.77, 0.8], 'alpha': 1}, 'E_KotoTunerTail': {'color': [0.92, 0.96, 1], 'alpha': 1}, 'E_PendulumBracket0': {'color': [0.25, 0.3, 0.34], 'alpha': 1}, 'E_PendulumBearing0': {'color': [0.73, 0.77, 0.8], 'alpha': 1}, 'E_PendulumBracket1': {'color': [0.25, 0.3, 0.34], 'alpha': 1}, 'E_PendulumBearing1': {'color': [0.73, 0.77, 0.8], 'alpha': 1}, 'F_KotoSpeakingString': {'color': [0.92, 0.96, 1], 'alpha': 1}, 'F_KotoBackString': {'color': [0.92, 0.96, 1], 'alpha': 1}, 'F_KotoThirdBridge': {'color': [0.48, 0.3, 0.16], 'alpha': 1}, 'F_KotoAnchorSaddle': {'color': [0.8, 0.63, 0.3], 'alpha': 1}, 'F_KotoAnchorPin': {'color': [0.73, 0.77, 0.8], 'alpha': 1}, 'F_KotoAnchorTail': {'color': [0.92, 0.96, 1], 'alpha': 1}, 'F_KotoTunerSaddle': {'color': [0.8, 0.63, 0.3], 'alpha': 1}, 'F_KotoTunerPin': {'color': [0.73, 0.77, 0.8], 'alpha': 1}, 'F_KotoTunerTail': {'color': [0.92, 0.96, 1], 'alpha': 1}, 'F_PendulumBracket0': {'color': [0.25, 0.3, 0.34], 'alpha': 1}, 'F_PendulumBearing0': {'color': [0.73, 0.77, 0.8], 'alpha': 1}, 'F_PendulumBracket1': {'color': [0.25, 0.3, 0.34], 'alpha': 1}, 'F_PendulumBearing1': {'color': [0.73, 0.77, 0.8], 'alpha': 1}, 'G_KotoSpeakingString': {'color': [0.92, 0.96, 1], 'alpha': 1}, 'G_KotoBackString': {'color': [0.92, 0.96, 1], 'alpha': 1}, 'G_KotoThirdBridge': {'color': [0.48, 0.3, 0.16], 'alpha': 1}, 'G_KotoAnchorSaddle': {'color': [0.8, 0.63, 0.3], 'alpha': 1}, 'G_KotoAnchorPin': {'color': [0.73, 0.77, 0.8], 'alpha': 1}, 'G_KotoAnchorTail': {'color': [0.92, 0.96, 1], 'alpha': 1}, 'G_KotoTunerSaddle': {'color': [0.8, 0.63, 0.3], 'alpha': 1}, 'G_KotoTunerPin': {'color': [0.73, 0.77, 0.8], 'alpha': 1}, 'G_KotoTunerTail': {'color': [0.92, 0.96, 1], 'alpha': 1}, 'G_PendulumBracket0': {'color': [0.25, 0.3, 0.34], 'alpha': 1}, 'G_PendulumBearing0': {'color': [0.73, 0.77, 0.8], 'alpha': 1}, 'G_PendulumBracket1': {'color': [0.25, 0.3, 0.34], 'alpha': 1}, 'G_PendulumBearing1': {'color': [0.73, 0.77, 0.8], 'alpha': 1}, 'A_KotoSpeakingString': {'color': [0.92, 0.96, 1], 'alpha': 1}, 'A_KotoBackString': {'color': [0.92, 0.96, 1], 'alpha': 1}, 'A_KotoThirdBridge': {'color': [0.48, 0.3, 0.16], 'alpha': 1}, 'A_KotoAnchorSaddle': {'color': [0.8, 0.63, 0.3], 'alpha': 1}, 'A_KotoAnchorPin': {'color': [0.73, 0.77, 0.8], 'alpha': 1}, 'A_KotoAnchorTail': {'color': [0.92, 0.96, 1], 'alpha': 1}, 'A_KotoTunerSaddle': {'color': [0.8, 0.63, 0.3], 'alpha': 1}, 'A_KotoTunerPin': {'color': [0.73, 0.77, 0.8], 'alpha': 1}, 'A_KotoTunerTail': {'color': [0.92, 0.96, 1], 'alpha': 1}, 'A_PendulumBracket0': {'color': [0.25, 0.3, 0.34], 'alpha': 1}, 'A_PendulumBearing0': {'color': [0.73, 0.77, 0.8], 'alpha': 1}, 'A_PendulumBracket1': {'color': [0.25, 0.3, 0.34], 'alpha': 1}, 'A_PendulumBearing1': {'color': [0.73, 0.77, 0.8], 'alpha': 1}, 'C_EccentricCam': {'color': [0.8, 0.63, 0.3], 'alpha': 1}, 'C_FollowerLever': {'color': [0.8, 0.63, 0.3], 'alpha': 1}, 'C_FollowerRoller': {'color': [0.25, 0.3, 0.34], 'alpha': 1}, 'C_RollerPin': {'color': [0.73, 0.77, 0.8], 'alpha': 1}, 'C_ReturnSpringEnvelope': {'color': [0.8, 0.63, 0.3], 'alpha': 1}, 'D_EccentricCam': {'color': [0.8, 0.63, 0.3], 'alpha': 1}, 'D_FollowerLever': {'color': [0.8, 0.63, 0.3], 'alpha': 1}, 'D_FollowerRoller': {'color': [0.25, 0.3, 0.34], 'alpha': 1}, 'D_RollerPin': {'color': [0.73, 0.77, 0.8], 'alpha': 1}, 'D_ReturnSpringEnvelope': {'color': [0.8, 0.63, 0.3], 'alpha': 1}, 'E_EccentricCam': {'color': [0.8, 0.63, 0.3], 'alpha': 1}, 'E_FollowerLever': {'color': [0.8, 0.63, 0.3], 'alpha': 1}, 'E_FollowerRoller': {'color': [0.25, 0.3, 0.34], 'alpha': 1}, 'E_RollerPin': {'color': [0.73, 0.77, 0.8], 'alpha': 1}, 'E_ReturnSpringEnvelope': {'color': [0.8, 0.63, 0.3], 'alpha': 1}, 'F_EccentricCam': {'color': [0.8, 0.63, 0.3], 'alpha': 1}, 'F_FollowerLever': {'color': [0.8, 0.63, 0.3], 'alpha': 1}, 'F_FollowerRoller': {'color': [0.25, 0.3, 0.34], 'alpha': 1}, 'F_RollerPin': {'color': [0.73, 0.77, 0.8], 'alpha': 1}, 'F_ReturnSpringEnvelope': {'color': [0.8, 0.63, 0.3], 'alpha': 1}, 'G_EccentricCam': {'color': [0.8, 0.63, 0.3], 'alpha': 1}, 'G_FollowerLever': {'color': [0.8, 0.63, 0.3], 'alpha': 1}, 'G_FollowerRoller': {'color': [0.25, 0.3, 0.34], 'alpha': 1}, 'G_RollerPin': {'color': [0.73, 0.77, 0.8], 'alpha': 1}, 'G_ReturnSpringEnvelope': {'color': [0.8, 0.63, 0.3], 'alpha': 1}, 'A_EccentricCam': {'color': [0.8, 0.63, 0.3], 'alpha': 1}, 'A_FollowerLever': {'color': [0.8, 0.63, 0.3], 'alpha': 1}, 'A_FollowerRoller': {'color': [0.25, 0.3, 0.34], 'alpha': 1}, 'A_RollerPin': {'color': [0.73, 0.77, 0.8], 'alpha': 1}, 'A_ReturnSpringEnvelope': {'color': [0.8, 0.63, 0.3], 'alpha': 1}, 'GuardBack': {'color': [0.65, 0.84, 0.88], 'alpha': 0.1}, 'GuardFront': {'color': [0.65, 0.84, 0.88], 'alpha': 0.1}, 'GuardRoof': {'color': [0.65, 0.84, 0.88], 'alpha': 0.1}, 'GuardLeft': {'color': [0.65, 0.84, 0.88], 'alpha': 0.1}, 'GuardRight': {'color': [0.65, 0.84, 0.88], 'alpha': 0.1}, 'ClockworkInputCoupling': {'color': [0.73, 0.77, 0.8], 'alpha': 1}}
for name,style in styles.items():
    o=doc.getObject(name)
    if not o:continue
    o.ViewObject.ShapeColor=tuple(float(c) for c in style['color'])
    if name.startswith('Guard'):o.ViewObject.Transparency=85
    if 'String' in name or 'Tail' in name:o.ViewObject.LineColor=(.92,.96,1.0);o.ViewObject.LineWidth=2.0
for o in doc.Objects:
    if o.TypeId in ['App::Line','App::Plane','App::Point','App::Origin'] or 'Profile' in o.Name:
        if o.ViewObject:o.ViewObject.Visibility=False
for o in doc.Objects:
    if o.ViewObject and o.TypeId in ['App::DocumentObjectGroup','App::Part','Part::Feature']:o.ViewObject.Visibility=True
def solve_cam(row,theta):
    U=V(0,row['pivot_y'],row['pivot_z']);C=V(0,-59-4*math.sin(theta),-116+4*math.cos(theta))
    v=C-U;d=v.Length;v.normalize();a=(row['lever_length']**2-15**2+d*d)/(2*d);h2=row['lever_length']**2-a*a
    assert h2>0,'Cam unreachable'
    P=U+v*a;perp=V(0,-v.z,v.y);h=math.sqrt(h2);b1=P+perp*h;b2=P-perp*h;B=b1 if b1.y>b2.y else b2
    return math.atan2(-(B.y-U.y),B.z-U.z),C,B

def update_cams(t):
    doc.Motion.Time=t
    for row in rows:
        theta=-math.radians(18*t*row['ratio']);beta,C,B=solve_cam(row,theta);delta=math.atan2(math.sin(beta-row['beta_mid']),math.cos(beta-row['beta_mid']))
        root=V(row['station'],row['pivot_y'],row['pivot_z'])
        doc.getObject(row['note']+'_LongArmRotor').Placement=App.Placement(root,App.Rotation(V(1,0,0),90+math.degrees(delta)))
        doc.getObject(row['note']+'_Rocker').Placement=App.Placement(root,App.Rotation(V(1,0,0),math.degrees(beta)))
    doc.recompute()

update_cams(0)
Gui.activateWorkbench('PartWorkbench')
view=Gui.activeDocument().activeView()
view.setCameraOrientation(App.Rotation(V(1,0,-.25),V(0,1,0),V(.25,.65,1),'ZXY').Q)
view.fitAll();doc.recompute();doc.save()
view.saveImage(OUT+'/Harpe_koto_native_preview.png',1800,1100,'Current')
if 'harpe_koto_timer' in globals():harpe_koto_timer.stop()
harpe_koto_start=time.monotonic()
harpe_koto_timer=QtCore.QTimer(Gui.getMainWindow())
def harpe_koto_tick():
    if doc.Name not in App.listDocuments():harpe_koto_timer.stop();return
    update_cams(time.monotonic()-harpe_koto_start)
harpe_koto_timer.timeout.connect(harpe_koto_tick)
harpe_koto_timer.start(100)
print('Koto cam drive running — prescribed kinematics, not a force simulation')
